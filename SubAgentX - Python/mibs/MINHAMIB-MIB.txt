MINHAMIB-MIB DEFINITIONS ::= BEGIN

IMPORTS
    MODULE-IDENTITY, OBJECT-TYPE, NOTIFICATION-TYPE, Integer32, Unsigned32, Counter32, Counter64, TimeTicks, IpAddress, enterprises
        FROM SNMPv2-SMI
    TEXTUAL-CONVENTION, DisplayString
        FROM SNMPv2-TC
    OBJECT-TYPE
		FROM RFC-1212
    MODULE-COMPLIANCE, OBJECT-GROUP, NOTIFICATION-GROUP
        FROM SNMPv2-CONF
    agentxObjects
        FROM AGENTX-MIB
   gerenciaUFRGS
        FROM BASE-MIB;

minhaMIB     OBJECT IDENTIFIER ::= { gerenciaUFRGS 1 }
informacoes  OBJECT IDENTIFIER ::= { minhaMIB 1 }
tabelas      OBJECT IDENTIFIER ::= { minhaMIB 2 }

-----------------------------------
--- Scalars
-----------------------------------
infoAlunos  OBJECT-TYPE
	SYNTAX     DisplayString
	ACCESS     read-only
	STATUS     mandatory
	DESCRIPTION 
		"Nome dos alunos pertencentes ao grupo"
	::= { informacoes 1 }
	
-----------------------------------
--- Tables
-----------------------------------
tbTesteCount OBJECT-TYPE
    SYNTAX Integer32
    ACCESS read-only
    STATUS mandatory
    DESCRIPTION
        "Numero de entradas na tabela Teste"
    ::= { tabelas 1 }

tbTeste OBJECT-TYPE
    SYNTAX SEQUENCE OF TbTesteEntry
    ACCESS not-accessible
    STATUS mandatory
    DESCRIPTION
        "Tabela de teste"
    ::= { tabelas 2 }

TbTesteEntry ::=
    SEQUENCE {
        tbTesteEntryIndex           Integer32,
        tbTesteEntryVogal           DisplayString,
        tbTesteEntryDescricao       DisplayString,
        tbTesteEntryPosicaoAlfabeto Integer32
    }

tbTesteEntry OBJECT-TYPE
    SYNTAX TbTesteEntry
    ACCESS not-accessible
    STATUS mandatory
    DESCRIPTION
        "Uma linha da tabela"
    INDEX { tbTesteEntryIndex }
    
    ::= { tbTeste 1 }

tbTesteEntryIndex OBJECT-TYPE
    SYNTAX Integer32
    ACCESS read-only
    STATUS mandatory
    DESCRIPTION
        "Coluna indice"   
    ::= { tbTesteEntry 1 }

tbTesteEntryVogal OBJECT-TYPE
    SYNTAX DisplayString
    ACCESS read-only
    STATUS mandatory
    DESCRIPTION
        "A vogal desta linha"    
    ::= { tbTesteEntry 2 }
 
tbTesteEntryDescricao OBJECT-TYPE
    SYNTAX DisplayString
    ACCESS read-only
    STATUS mandatory
    DESCRIPTION
        "Descricao da vogal"    
    ::= { tbTesteEntry 3 }

tbTesteEntryPosicaoAlfabeto OBJECT-TYPE
    SYNTAX Integer32
    ACCESS read-only
    STATUS mandatory
    DESCRIPTION
        "Posicao da vogal no alfabeto"    
    ::= { tbTesteEntry 4 }

END
